module apply-config-template {
 /*
  * Copyright 2017 Sebastian Strollo
  *
  * Licensed under the Apache License, Version 2.0 (the "License");
  * you may not use this file except in compliance with the License.
  * You may obtain a copy of the License at
  *
  *     https://www.apache.org/licenses/LICENSE-2.0
  *
  * Unless required by applicable law or agreed to in writing, software
  * distributed under the License is distributed on an "AS IS" BASIS,
  * WITHOUT WARRANTIES OR CONDITIONS OF ANY KIND, either express or implied.
  * See the License for the specific language governing permissions and
  * limitations under the License.
  **/
  namespace "http://example.com/ns/apply-config-template";
  prefix apply-config-template;

  import tailf-common {
    prefix tailf;
  }

  import tailf-ncs {
    prefix ncs;
  }

  description
    "An Example action which can apply config templates in NSO.";

  revision 2017-09-19 {
    description "Initial revision.";
  }

  container template {
    tailf:action apply-config-template {
      tailf:actionpoint apply-config-template-action;
      input {
        leaf name {
          description "The name of the template";
          type string;
          tailf:non-strict-leafref {
            path "/ncs:packages/ncs:package/ncs:templates";
          }
          mandatory true;
        }
        leaf context-node {
          description
            "A keypath to the context node. The context node will be
             used for all XPath expressions in the template.";
          type string;
          default "/";
        }
        list variable {
          description "A list of variable bindings passed to the template.";
          key name;
          leaf name {
            description "Variable name";
            type string {
              length 1..1024;
            }
          }
          leaf value {
            description "Variable value";
            type string;
            default "";
          }
        }
      }
    }
  }
}
