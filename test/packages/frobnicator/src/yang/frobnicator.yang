module frobnicator {
  namespace "http://www.example.com/ns/frobnicator";
  prefix frb;

  description "A made up device model for testing.";

  container frobnicator {
    leaf system-name {
      type string;
    }
    choice foo {
      leaf a {
        type string;
      }
      leaf b {
        type uint32;
      }
    }
    list rules {
      key name;
      ordered-by user;
      leaf name {
        type string;
      }
      leaf value {
        type uint32;
      }
      leaf action {
        type enumeration {
          enum allow;
          enum deny;
        }
      }
      leaf drop {
        type empty;
      }
    }
  }
}
